FME workspace TP2.fmw

Parameters:
- SourceDataset_GEOJSON_18 = https://www.donneesquebec.ca/recherche/dataset/2d3b5cf8-b347-49c7-ad3b-bd6a9c15e443/resource/fc806a50-7e84-4f39-acae-69069e4784bf/download/es_collegial.geojson   # Source GeoJSON File or URL
- SourceDataset_GEOJSON_13 = https://www.donneesquebec.ca/recherche/dataset/2d3b5cf8-b347-49c7-ad3b-bd6a9c15e443/resource/f93b5275-9708-4de2-aea3-38273753694d/download/es_universitaire.geojson   # Source GeoJSON File or URL
- SourceDataset_GEOJSON = https://donnees.montreal.ca/fr/dataset/1eee09ec-d3b8-4c7d-ab6d-e85eb9fdd0b0/resource/4eab2cee-0ee4-4dd3-93c3-2a476173b8ec/download/eqsante.json   # Source GeoJSON File or URL
- SourceDataset_GEOJSON_20 = https://donnees.montreal.ca/dataset/c1d65779-d3cb-44e8-af0a-b9f2c5f7766d/resource/ece728c7-6f2d-4a51-a36d-21cd70e0ddc7/download/businesses.geojson   # Source GeoJSON File or URL
- SourceDataset_SHAPEFILE = https://www.stm.info/sites/default/files/gtfs/stm_sig.zip   # Source Esri Shapefile(s)
- SourceDataset_GEOJSON_21 = https://donnees.montreal.ca/fr/dataset/2e9e4d2f-173a-4c3d-a5e3-565d79baa27d/resource/35796624-15df-4503-a569-797665f8768e/download/espace_vert.json   # Source GeoJSON File or URL
- SourceDataset_GEOJSON_15 = https://donnees.montreal.ca/fr/dataset/91f66001-b461-4f63-aff4-cddc0fe30ffe/resource/c9d0b8d6-c7a6-4766-a5cc-98e8b1392bbc/download/pdq.geojson   # Source GeoJSON File or URL
- SourceDataset_GEOJSON_12 = https://donnees.montreal.ca/dataset/5829b5b0-ea6f-476f-be94-bc2b8797769a/resource/aacc4576-97b3-4d8d-883d-22bbca41dbe6/download/actes-criminels.geojson   # Source GeoJSON File or URL
- SourceDataset_GEOJSON_14 = https://donnees.montreal.ca/fr/dataset/c69e78c6-e454-4bd9-9778-e4b0eaf8105b/resource/beff8ce0-7a61-4a82-95b5-96d89bafa671/download/casernes.geojson   # Source GeoJSON File or URL
- SourceDataset_GEOJSON_17 = https://donnees.montreal.ca/dataset/limites-administratives-agglomeration/resource/6b313375-d9bc-4dc3-af8e-ceae3762ae6e/download   # Source GeoJSON File or URL
- DestDataset_POSTGIS = geo7630h25   # Connection

Readers:
- GEOJSON_1: GEOJSON from $(SourceDataset_GEOJSON)
- GEOJSON_2: GEOJSON from $(SourceDataset_GEOJSON_18)
- GEOJSON_3: GEOJSON from $(SourceDataset_GEOJSON_13)
- GEOJSON_4: GEOJSON from $(SourceDataset_GEOJSON_20)
- SHAPEFILE_1: SHAPEFILE from $(SourceDataset_SHAPEFILE)
- GEOJSON_5: GEOJSON from $(SourceDataset_GEOJSON_21)
- GEOJSON_6: GEOJSON from $(SourceDataset_GEOJSON_15)
- GEOJSON_7: GEOJSON from $(SourceDataset_GEOJSON_12)
- GEOJSON_8: GEOJSON from $(SourceDataset_GEOJSON_14)
- GEOJSON_9: GEOJSON from $(SourceDataset_GEOJSON_17)

Writers:
- POSTGIS_1: POSTGIS to $(DestDataset_POSTGIS)

Note: Géneration d'une grille Hexagonale (mais comme pour l'examen on doit reprojeter nos données vu que le H3indexer accepte le 4326 en entrée puis un autre reporjeteur pour que notre sortie soit dans le systeme voulu )
AttributeFilter_5
    ATTR_NAME = Nom
    ATTR_VALUES = <Empty>,<Missing>,<Null>,<Unfiltered>
    <UNFILTERED> -> Reprojector_10
Note: Transformation des polygone de parcs en points
Note: cette etape consiste a deduire le minimum et le maximum de chaque comodité
Note: Cette étape m'a permis de créer et calculer les scores que je cherche comme le (max-min) et les score normalisés et pondérés
RandomPointGenerator
    DENSIFY_FACTOR = 2
    MIN_NUM = 10
    NUM_POINTS = 1913
    Point -> PointOnAreaOverlayer_9 [POINT]
Note: ce sont nos données d'entrée en format GeoJson/CSV/SHP
Note: Suppression des attributs non necessaires dans le but d'effectuer un petit nettoyage (ex date de modification de la données)
Note: L'attribute filter nous permets d'utiliser les données qu'on souhaite analysé / Par ex :le fichier des université et college qui provient des données du quebec donc je dois refiltrer sur montreal
Note: Filtrage des crimes sans coordonées
Note: reprojection de mes données dans le systéme voulu qui est le 3852
Note: J'ai lié un tester afin de confirmer que tout mes sont sortie n'ont pas de valeur null ou missing et si c'est le cas ca fait un genre de filtre
Note: le PointOnAreaOverlayer nous permets de determiner le nombre de comodités total dans chaque hexagone crée (ce qui definie combien de comodités ou de critére notre hexagone contient )
AttributeFilter_4
    ATTR_NAME = LONGITUDE
    ATTR_VALUES = <Empty>,<Missing>,<Null>,<Unfiltered>
    <UNFILTERED> -> Reprojector
Note: ce transformateur m'a permis d'extraire les coordonnées des point s qui n'ont pas cette attribut
AttributeFilter
    ATTR_NAME = NOM_MUNCP
    ATTR_VALUES = <Empty>,<Missing>,<Null>,<Unfiltered>,Montréal
    Montréal -> Reprojector_4
AttributeFilter_2
    ATTR_NAME = NOM_MUNCP
    ATTR_VALUES = <Empty>,<Missing>,<Null>,<Unfiltered>,Montréal
    Montréal -> Reprojector_7
AttributeFilter_3
    ATTR_NAME = statut
    ATTR_VALUES = <Empty>,<Missing>,<Null>,<Unfiltered>,Ouvert
    Ouvert -> Reprojector_8
Note: Calcul du score de Quartier et attribuer un classement des quariers de mauvais a excellent
TP2_H25 (writer POSTGIS_1)
    attributes: score_quartier float8, score_securité float8, score_education float8, score_attraction float8, score_police_pondéré float8, nom_officiel varchar, nbr_poste_police int8, score_crime_ponderé float8, nbr_crimes int8, score_caserne_ponderé float8, nbr_caserne_pompier int8, score_santé_pondere float8, nbr_hopitaux int8, score_collége_ponderé float8, nbr_college int8, score_université_ponderé float8, nbr_université int8, score_commerces_pondéré float8, nbr_resto_commerces int8, score_stm_pondéré float8, nbr_arret_stm int8, score_parcs_ponderé float8, nbr_parc int8, classe varchar
Note: Afin d'eviter toutes erreurs ,on se doit je faire une jointure entre nos données vu qu'il proviennent de sources et de couches differentes ,pour cette jointure on utilise le numero de l'hexagone afin de les joindre et associer
Note: petit nettoyage : exemple j'enleve les valeurs min et max
FeatureJoiner_8__Rejected_: Logger
    LOG_FEATURE = LOG_ONLY
    MAXCOORDS = 20
    MAXFEATS = 20
    MESSAGE = Feature is:
    SEVERITY = INFO

Bookmark: Données d'entrée
espvert.esv_espace_vert_vue_datefin_null (reader GEOJSON_5)
    attributes: OBJECTID string, Type string, Lien string, Nom string, NUM_INDEX string, SUPERFICIE string, PROPRIETE string, GESTION string, COMPETENCE string, TYPO1 string, TYPO2 string
    -> AttributeManager
PDQ (reader GEOJSON_6)
    attributes: NO_CIV_LIE string, PREFIX_TEM string, NOM_TEMP string, DIR_TEMP string, MUN_TEMP string, DESC_LIEU string, LATITUDE string, LONGITUDE string, X string, Y string
    -> AttributeManager_3
actes-criminels (reader GEOJSON_7)
    attributes: CATEGORIE string, DATE string, QUART string, PDQ float, X float, Y float, LONGITUDE float, LATITUDE float
    -> AttributeManager_2
casernes (reader GEOJSON_8)
    attributes: CASERNE string, NO_CIVIQUE string, RUE string, LATITUDE string, LONGITUDE string, ARRONDISSEMENT string, VILLE string, DATE_DEBUT string, DATE_FIN string, MTM8_X float, MTM8_Y float
    -> AttributeManager_5
EqSante (reader GEOJSON_1)
    attributes: Etablissem string, MISSION string, Numero string, MetroAgglo string
    -> AttributeManager_6
ES_Collegial (reader GEOJSON_2)
    attributes: OBJECTID int, DT_MAJ_GDUNO string, CD_ORGNS string, NOM_COURT string, NOM_OFFCL string, ADRS_GEO_L1_GDUNO string, ADRS_GEO_L2_GDUNO string, CD_MUNCP string, NOM_MUNCP string, STAT_MUNCP string, CD_POSTL_GDUNO string, TYPE_ORGNS string, RESEAU string, SITE_WEB string, COORD_X_LL84 float, COORD_Y_LL84 float, ORDRE_ENS string, STYLE_CART string
    -> AttributeManager_7
ES_Universitaire (reader GEOJSON_3)
    attributes: OBJECTID int, DT_MAJ_GDUNO string, CD_ORGNS string, NOM_COURT string, NOM_OFFCL string, ADRS_GEO_L1_GDUNO string, ADRS_GEO_L2_GDUNO string, CD_MUNCP string, NOM_MUNCP string, STAT_MUNCP string, CD_POSTL_GDUNO string, TYPE_ORGNS string, RESEAU string, SITE_WEB string, COORD_X_LL84 float, COORD_Y_LL84 float, ORDRE_ENS string, STYLE_CART string
    -> AttributeManager_8
businesses (reader GEOJSON_4)
    attributes: business_id int, name string, address string, city string, state string, type string, statut string, date_statut string, latitude string, longitude string, x float, y float
    -> AttributeManager_4
stm_arrets_sig (reader SHAPEFILE_1)
    attributes: stop_code long, stop_id varchar(8), stop_name varchar(75), stop_url varchar(100), wheelchair short, route_id varchar(64), loc_type short, shelter short, service_id varchar(3)
    -> AttributeManager_9
download (reader GEOJSON_9)
    attributes: CODEID int, NOM string, NOM_OFFICIEL string, CODEMAMH string, CODE_3C string, NUM int, ABREV string, TYPE string, COMMENT string, DATEMODIF string
    -> AttributeManager_10

Bookmark: Suppression des attributs nin necessaires
AttributeManager
    ATTR_TABLE:
      REMOVE OBJECTID (buffer)
      REMOVE Type (buffer)
      REMOVE Lien (buffer)
      REMOVE NUM_INDEX (buffer)
      REMOVE PROPRIETE (buffer)
      REMOVE GESTION (buffer)
      REMOVE COMPETENCE (buffer)
      REMOVE TYPO1 (buffer)
      REMOVE TYPO2 (buffer)
    -> CoordinateExtractor_5
AttributeManager_3
    ATTR_TABLE:
      REMOVE NO_CIV_LIE (buffer)
      REMOVE PREFIX_TEM (buffer)
      REMOVE NOM_TEMP (buffer)
      REMOVE DIR_TEMP (buffer)
      REMOVE MUN_TEMP (buffer)
      REMOVE DESC_LIEU (buffer)
    -> Reprojector_3
AttributeManager_2
    ATTR_TABLE:
      REMOVE CATEGORIE (buffer)
      REMOVE DATE (buffer)
      REMOVE QUART (buffer)
      REMOVE PDQ (real64)
    -> AttributeFilter_4
AttributeManager_5
    ATTR_TABLE:
      REMOVE CASERNE (buffer)
      REMOVE NO_CIVIQUE (buffer)
      REMOVE RUE (buffer)
      REMOVE ARRONDISSEMENT (buffer)
      REMOVE VILLE (buffer)
      REMOVE DATE_DEBUT (buffer)
      REMOVE DATE_FIN (buffer)
    -> Reprojector_5
AttributeManager_6
    ATTR_TABLE:
      REMOVE MISSION (buffer)
      REMOVE Numero (buffer)
      REMOVE MetroAgglo (buffer)
    -> CoordinateExtractor
AttributeManager_7
    ATTR_TABLE:
      REMOVE OBJECTID (int64)
      REMOVE DT_MAJ_GDUNO (buffer)
      REMOVE CD_ORGNS (buffer)
      REMOVE NOM_COURT (buffer)
      REMOVE ADRS_GEO_L1_GDUNO (buffer)
      REMOVE ADRS_GEO_L2_GDUNO (buffer)
      REMOVE CD_MUNCP (buffer)
      REMOVE STAT_MUNCP (buffer)
      REMOVE CD_POSTL_GDUNO (buffer)
      REMOVE TYPE_ORGNS (buffer)
      REMOVE RESEAU (buffer)
      REMOVE SITE_WEB (buffer)
      REMOVE ORDRE_ENS (buffer)
      REMOVE STYLE_CART (buffer)
    -> CoordinateExtractor_2
AttributeManager_8
    ATTR_TABLE:
      REMOVE OBJECTID (int64)
      REMOVE DT_MAJ_GDUNO (buffer)
      REMOVE CD_ORGNS (buffer)
      REMOVE NOM_COURT (buffer)
      REMOVE ADRS_GEO_L1_GDUNO (buffer)
      REMOVE ADRS_GEO_L2_GDUNO (buffer)
      REMOVE CD_MUNCP (buffer)
      REMOVE STAT_MUNCP (buffer)
      REMOVE CD_POSTL_GDUNO (buffer)
      REMOVE TYPE_ORGNS (buffer)
      REMOVE RESEAU (buffer)
      REMOVE SITE_WEB (buffer)
      REMOVE ORDRE_ENS (buffer)
      REMOVE STYLE_CART (buffer)
    -> CoordinateExtractor_3
AttributeManager_4
    ATTR_TABLE:
      REMOVE business_id (int64)
      REMOVE address (buffer)
      REMOVE city (buffer)
      REMOVE state (buffer)
      REMOVE type (buffer)
      REMOVE date_statut (buffer)
    -> AttributeFilter_3
AttributeManager_9
    ATTR_TABLE:
      REMOVE stop_code (int32)
      REMOVE stop_id (varchar(8))
      REMOVE stop_url (varchar(100))
      REMOVE wheelchair (int16)
      REMOVE route_id (varchar(64))
      REMOVE loc_type (int16)
      REMOVE shelter (int16)
      REMOVE service_id (varchar(3))
    -> CoordinateExtractor_4
AttributeManager_10
    ATTR_TABLE:
      REMOVE CODEID (int64)
      REMOVE NOM (buffer)
      REMOVE CODEMAMH (buffer)
      REMOVE CODE_3C (buffer)
      REMOVE NUM (int64)
      REMOVE ABREV (buffer)
      REMOVE TYPE (buffer)
      REMOVE COMMENT (buffer)
      REMOVE DATEMODIF (buffer)
    -> Reprojector_2

Bookmark: Extracteur de coordonnées
CoordinateExtractor_5
    IND = 0
    RECURSIVE = No
    X_ATTR = LONGITUDE
    Y_ATTR = LATITUDE
    MODE = Specify Coordinate
    -> AttributeFilter_5
CoordinateExtractor
    IND = 0
    RECURSIVE = No
    X_ATTR = LONGITUDE
    Y_ATTR = LATITUDE
    MODE = Specify Coordinate
    -> Reprojector_6
CoordinateExtractor_2
    IND = 0
    RECURSIVE = No
    X_ATTR = LONGITUDE
    Y_ATTR = LATITUDE
    MODE = Specify Coordinate
    -> AttributeFilter
CoordinateExtractor_3
    IND = 0
    RECURSIVE = No
    X_ATTR = LONGITUDE
    Y_ATTR = LATITUDE
    MODE = Specify Coordinate
    -> AttributeFilter_2
CoordinateExtractor_4
    IND = 0
    RECURSIVE = No
    X_ATTR = LONGITUDE
    Y_ATTR = LATITUDE
    MODE = Specify Coordinate
    -> Reprojector_9

Bookmark: Reprojection
Reprojector_10
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_9
Reprojector_3
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester
Reprojector
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_2
Reprojector_5
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_3
Reprojector_6
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_4
Reprojector_4
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_5
Reprojector_7
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_6
Reprojector_8
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_7
Reprojector_9
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Tester_8

Bookmark: Tester
Tester_9
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> RandomPointGenerator [Area]
Tester
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer [POINT]
Tester_2
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_2 [POINT]
Tester_3
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_3 [POINT]
Tester_4
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_4 [POINT]
Tester_5
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_5 [POINT]
Tester_6
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_6 [POINT]
Tester_7
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_7 [POINT]
Tester_8
    BOOL_OP = OR
    TEST_CLAUSE:
      TEST LATITUDE ATTRIBUTE_VALUE_NULL ""
      TEST LONGITUDE ATTRIBUTE_VALUE_NULL ""
      TEST Y ATTRIBUTE_VALUE_NULL ""
      TEST X ATTRIBUTE_VALUE_NULL ""
    TEST_MODE = TEST
    FAILED -> PointOnAreaOverlayer_8 [POINT]

Bookmark: Generation d'un Grille Hexagonale
Reprojector_2
    DEST = EPSG:4326
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> H3HexagonalIndexer
H3HexagonalIndexer
    INDEX_OPERATION = Filling Indexes
    -> EsriReprojector_3
    <REJECTED> -> H3HexagonalIndexer__Rejected_
EsriReprojector_3
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = <None>
    INTERPOLATION_TYPE = ,NearestNeighbor
    RASTER_CELL_SIZE_LOOKUP = ,PreserveCells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    INTERPOLATION_TYPE_NAME = Nearest Neighbor
    RASTER_CELL_SIZE = Preserve Cells
    REPROJECTED -> PointOnAreaOverlayer [AREA]
    REPROJECTED -> PointOnAreaOverlayer_2 [AREA]
    REPROJECTED -> PointOnAreaOverlayer_3 [AREA]
    REPROJECTED -> PointOnAreaOverlayer_4 [AREA]
    REPROJECTED -> PointOnAreaOverlayer_5 [AREA]
    REPROJECTED -> PointOnAreaOverlayer_6 [AREA]
    REPROJECTED -> PointOnAreaOverlayer_7 [AREA]
    REPROJECTED -> PointOnAreaOverlayer_8 [AREA]
    REPROJECTED -> PointOnAreaOverlayer_9 [AREA]
H3HexagonalIndexer__Rejected_: Logger
    LOG_FEATURE = LOG_ONLY
    MAXCOORDS = 20
    MAXFEATS = 20
    MESSAGE = Feature is:
    SEVERITY = INFO

Bookmark: Calcul des point a l'interieur des Hexagones
PointOnAreaOverlayer
    DEAGGREGATE_INPUT = Yes
    OV_ATTR = nbr_poste_police
    POLYS_FIRST = NO
    AREA -> StatisticsCalculator_3
    <REJECTED> -> PointOnAreaOverlayer__Rejected_
Note: Le logger c'est important pour voir si on a des erreurs
PointOnAreaOverlayer__Rejected_: Logger
    LOG_FEATURE = LOG_ONLY
    MAXCOORDS = 20
    MAXFEATS = 20
    MESSAGE = Feature is:
    SEVERITY = INFO
PointOnAreaOverlayer_2
    DEAGGREGATE_INPUT = Yes
    OV_ATTR = Nbr_crimes
    POLYS_FIRST = NO
    AREA -> StatisticsCalculator_2
    <REJECTED> -> PointOnAreaOverlayer_2__Rejected_
PointOnAreaOverlayer_2__Rejected_: Logger
    LOG_FEATURE = LOG_ONLY
    MAXCOORDS = 20
    MAXFEATS = 20
    MESSAGE = Feature is:
    SEVERITY = INFO
PointOnAreaOverlayer_3
    DEAGGREGATE_INPUT = Yes
    OV_ATTR = Nbr_Caserne_pompier
    POLYS_FIRST = NO
    AREA -> StatisticsCalculator
    <REJECTED> -> PointOnAreaOverlayer_3__Rejected_
PointOnAreaOverlayer_3__Rejected_: Logger
    LOG_FEATURE = LOG_ONLY
    MAXCOORDS = 20
    MAXFEATS = 20
    MESSAGE = Feature is:
    SEVERITY = INFO
PointOnAreaOverlayer_4
    DEAGGREGATE_INPUT = Yes
    OV_ATTR = Nbr_hopitaux
    POLYS_FIRST = NO
    AREA -> StatisticsCalculator_4
    <REJECTED> -> PointOnAreaOverlayer_4__Rejected_
PointOnAreaOverlayer_4__Rejected_: Logger
    LOG_FEATURE = LOG_ONLY
    MAXCOORDS = 20
    MAXFEATS = 20
    MESSAGE = Feature is:
    SEVERITY = INFO
PointOnAreaOverlayer_5
    DEAGGREGATE_INPUT = Yes
    OV_ATTR = Nbr_college
    POLYS_FIRST = NO
    AREA -> StatisticsCalculator_5
    <REJECTED> -> PointOnAreaOverlayer_5__Rejected_
PointOnAreaOverlayer_5__Rejected_: Logger
    LOG_FEATURE = LOG_ONLY
    MAXCOORDS = 20
    MAXFEATS = 20
    MESSAGE = Feature is:
    SEVERITY = INFO
PointOnAreaOverlayer_6
    DEAGGREGATE_INPUT = Yes
    OV_ATTR = Nbr_université
    POLYS_FIRST = NO
    AREA -> StatisticsCalculator_6
    <REJECTED> -> PointOnAreaOverlayer_6__Rejected_
PointOnAreaOverlayer_6__Rejected_: Logger
    LOG_FEATURE = LOG_ONLY
    MAXCOORDS = 20
    MAXFEATS = 20
    MESSAGE = Feature is:
    SEVERITY = INFO
PointOnAreaOverlayer_7
    DEAGGREGATE_INPUT = Yes
    OV_ATTR = nbr_resto_commerces
    POLYS_FIRST = NO
    AREA -> StatisticsCalculator_7
    <REJECTED> -> PointOnAreaOverlayer_7__Rejected_
PointOnAreaOverlayer_7__Rejected_: Logger
    LOG_FEATURE = LOG_ONLY
    MAXCOORDS = 20
    MAXFEATS = 20
    MESSAGE = Feature is:
    SEVERITY = INFO
PointOnAreaOverlayer_8
    DEAGGREGATE_INPUT = Yes
    OV_ATTR = Nbr_Arret_STM
    POLYS_FIRST = NO
    AREA -> StatisticsCalculator_8
    <REJECTED> -> PointOnAreaOverlayer_8__Rejected_
PointOnAreaOverlayer_8__Rejected_: Logger
    LOG_FEATURE = LOG_ONLY
    MAXCOORDS = 20
    MAXFEATS = 20
    MESSAGE = Feature is:
    SEVERITY = INFO
PointOnAreaOverlayer_9
    DEAGGREGATE_INPUT = Yes
    OV_ATTR = Nbr_parc
    POLYS_FIRST = NO
    AREA -> StatisticsCalculator_9
    <REJECTED> -> PointOnAreaOverlayer_9__Rejected_
PointOnAreaOverlayer_9__Rejected_: Logger
    LOG_FEATURE = LOG_ONLY
    MAXCOORDS = 20
    MAXFEATS = 20
    MESSAGE = Feature is:
    SEVERITY = INFO

Bookmark: Extraction de données
StatisticsCalculator_3
    ATTR_ACCUM_MODE = None
    CALCULATION_MODE = NUMERIC
    FEAT_STATS = nbr_poste_police,NUMERIC_MODE,MIN,MAX,,,,,,,,,,,
    COMPLETE -> AttributeCreator
StatisticsCalculator_2
    ATTR_ACCUM_MODE = None
    CALCULATION_MODE = NUMERIC
    FEAT_STATS = Nbr_crimes,NUMERIC_MODE,MIN,MAX,,,,,,,,,,,
    COMPLETE -> AttributeCreator_2
StatisticsCalculator
    ATTR_ACCUM_MODE = None
    CALCULATION_MODE = NUMERIC
    FEAT_STATS = Nbr_Caserne_pompier,NUMERIC_MODE,MIN,MAX,,,,,,,,,,,
    COMPLETE -> AttributeCreator_3
StatisticsCalculator_4
    ATTR_ACCUM_MODE = None
    CALCULATION_MODE = NUMERIC
    FEAT_STATS = Nbr_hopitaux,NUMERIC_MODE,MIN,MAX,,,,,,,,,,,
    COMPLETE -> AttributeCreator_4
StatisticsCalculator_5
    ATTR_ACCUM_MODE = None
    CALCULATION_MODE = NUMERIC
    FEAT_STATS = Nbr_college,NUMERIC_MODE,MIN,MAX,,,,,,,,,,,
    COMPLETE -> AttributeCreator_5
StatisticsCalculator_6
    ATTR_ACCUM_MODE = None
    CALCULATION_MODE = NUMERIC
    FEAT_STATS = Nbr_université,NUMERIC_MODE,MIN,MAX,,,,,,,,,,,
    COMPLETE -> AttributeCreator_6
StatisticsCalculator_7
    ATTR_ACCUM_MODE = None
    CALCULATION_MODE = NUMERIC
    FEAT_STATS = nbr_resto_commerces,NUMERIC_MODE,MIN,MAX,,,,,,,,,,,
    COMPLETE -> AttributeCreator_7
StatisticsCalculator_8
    ATTR_ACCUM_MODE = None
    CALCULATION_MODE = NUMERIC
    FEAT_STATS = Nbr_Arret_STM,NUMERIC_MODE,MIN,MAX,,,,,,,,,,,
    COMPLETE -> AttributeCreator_8
StatisticsCalculator_9
    ATTR_ACCUM_MODE = None
    CALCULATION_MODE = NUMERIC
    FEAT_STATS = Nbr_parc,NUMERIC_MODE,MIN,MAX,,,,,,,,,,,
    COMPLETE -> AttributeCreator_9

Bookmark: Calcul de nouvelles données
AttributeCreator
    ATTR_TABLE:
      SET_TO max-min (real64) = @Evaluate(@Value(nbr_poste_police.max)-@Value(nbr_poste_police.min)

        )
      SET_TO x-min (real64) = @Evaluate(@Value(nbr_poste_police)-@Value(nbr_poste_police.min))
      SET_TO Score_Police_Norm (real64) = @Evaluate(@Value(x-min)/@Value(max-min))
      SET_TO SCORE_POLICE (real64) = @Evaluate((@Value(Score_Police_Norm)*6)+1)
      SET_TO Score_Police_Pondéré (real64) = @Evaluate(@Value(SCORE_POLICE)*0.15)
    -> FeatureJoiner [LEFT]
AttributeCreator_2
    ATTR_TABLE:
      SET_TO max-min (real64) = @Evaluate(@Value(Nbr_crimes.max)-@Value(Nbr_crimes.min)

        )
      SET_TO x-min (real64) = @Evaluate(@Value(Nbr_crimes)-@Value(Nbr_crimes.min))
      SET_TO Score_Crime_Norm (real64) = @Evaluate(@Value(x-min)/@Value(max-min))
      SET_TO Score_crime (real64) = @Evaluate(7-(@Value(Score_Crime_Norm)*6))
      SET_TO Score_crime_ponderé (real64) = @Evaluate(@Value(Score_crime)*(-0.15))
    -> FeatureJoiner [RIGHT]
AttributeCreator_3
    ATTR_TABLE:
      SET_TO max-min (real64) = @Evaluate(@Value(Nbr_Caserne_pompier.max)-@Value(Nbr_Caserne_pompier.min)

        )
      SET_TO x-min (real64) = @Evaluate(@Value(Nbr_Caserne_pompier)-@Value(Nbr_Caserne_pompier.min))
      SET_TO Score_Caserne_NORM (real64) = @Evaluate(@Value(x-min)/@Value(max-min))
      SET_TO Score_Caserne (real64) = @Evaluate(@Value(Score_Caserne_NORM)*6+1)
      SET_TO Score_Caserne_Ponderé (real64) = @Evaluate(@Value(Score_Caserne)*0.15)
    -> FeatureJoiner_2 [RIGHT]
AttributeCreator_4
    ATTR_TABLE:
      SET_TO max-min (real64) = @Evaluate(@Value(Nbr_hopitaux.max)-@Value(Nbr_hopitaux.min)

        )
      SET_TO x-min (real64) = @Evaluate(@Value(Nbr_hopitaux)-@Value(Nbr_hopitaux.min))
      SET_TO Score_Santé_Norm (real64) = @Evaluate(@Value(x-min)/@Value(max-min))
      SET_TO Score_Santé (real64) = @Evaluate(@Value(Score_Santé_Norm)*6+1

        )
      SET_TO Score_Santé_Pondere (real64) = @Evaluate(@Value(Score_Santé)*0.15)
    -> FeatureJoiner_3 [RIGHT]
AttributeCreator_5
    ATTR_TABLE:
      SET_TO max-min (real64) = @Evaluate(@Value(Nbr_college.max)-@Value(Nbr_college.min)

        )
      SET_TO x-min (real64) = @Evaluate(@Value(Nbr_college)-@Value(Nbr_college.min))
      SET_TO Score_college_norm (real64) = @Evaluate(@Value(x-min)/@Value(max-min))
      SET_TO Score_Collége (real64) = @Evaluate(@Value(Score_college_norm)*6+1)
      SET_TO Score_Collége_Ponderé (real64) = @Evaluate(@Value(Score_Collége)*0.075)
    -> FeatureJoiner_4 [RIGHT]
AttributeCreator_6
    ATTR_TABLE:
      SET_TO max-min (real64) = @Evaluate(@Value(Nbr_université.max)-@Value(Nbr_université.min)

        )
      SET_TO x-min (real64) = @Evaluate(@Value(Nbr_université)-@Value(Nbr_université.min))
      SET_TO Score_Universite_Norm (real64) = @Evaluate(@Value(x-min)/@Value(max-min))
      SET_TO Score_Université (real64) = @Evaluate(@Value(Score_Universite_Norm)*6+1
        )
      SET_TO Score_Université_Ponderé (real64) = @Evaluate(@Value(Score_Université)*0.075
        )
    -> FeatureJoiner_5 [RIGHT]
AttributeCreator_7
    ATTR_TABLE:
      SET_TO max-min (real64) = @Evaluate(@Value(nbr_resto_commerces.max)-@Value(nbr_resto_commerces.min)

        )
      SET_TO x-min (real64) = @Evaluate(@Value(nbr_resto_commerces)-@Value(nbr_resto_commerces.min))
      SET_TO Score_Commerces_norm (real64) = @Evaluate(@Value(x-min)/@Value(max-min))
      SET_TO Score_Commerces (real64) = @Evaluate(@Value(Score_Commerces_norm)*6+1
        )
      SET_TO Score_Commerces_Pondéré (real64) = @Evaluate(@Value(Score_Commerces)*0.10)
    -> FeatureJoiner_6 [RIGHT]
AttributeCreator_8
    ATTR_TABLE:
      SET_TO max-min (real64) = @Evaluate(@Value(Nbr_Arret_STM.max)-@Value(Nbr_Arret_STM.min))
      SET_TO x-min (real64) = @Evaluate(@Value(Nbr_Arret_STM)-@Value(Nbr_Arret_STM.min))
      SET_TO Score_STM_Norm (real64) = @Evaluate(@Value(x-min)/@Value(max-min))
      SET_TO Score_STM (real64) = @Evaluate(@Value(Score_STM_Norm)*6+1
        )
      SET_TO Score_STM_pondéré (real64) = @Evaluate(@Value(Score_STM)*0.10)
    -> FeatureJoiner_7 [RIGHT]
AttributeCreator_9
    ATTR_TABLE:
      SET_TO max-min (real64) = @Evaluate(@Value(Nbr_parc.max)-@Value(Nbr_parc.min))
      SET_TO x-min (real64) = @Evaluate(@Value(Nbr_parc)-@Value(Nbr_parc.min))
      SET_TO Score_Parcs_Norm (real64) = @Evaluate(@Value(x-min)/@Value(max-min))
      SET_TO Score_Parcs (real64) = @Evaluate(@Value(Score_Parcs_Norm)*6+1)
      SET_TO Score_Parcs_ponderé (real64) = @Evaluate(@Value(Score_Parcs)*0.05)
    -> FeatureJoiner_8 [RIGHT]

Bookmark: Joindre les entitées
FeatureJoiner
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_2 [LEFT]
    <REJECTED> -> FeatureJoiner__Rejected_
FeatureJoiner__Rejected_: Logger
    LOG_FEATURE = LOG_ONLY
    MAXCOORDS = 20
    MAXFEATS = 20
    MESSAGE = Feature is:
    SEVERITY = INFO
FeatureJoiner_2
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_3 [LEFT]
    <REJECTED> -> FeatureJoiner_2__Rejected_
FeatureJoiner_2__Rejected_: Logger
    LOG_FEATURE = LOG_ONLY
    MAXCOORDS = 20
    MAXFEATS = 20
    MESSAGE = Feature is:
    SEVERITY = INFO
FeatureJoiner_3
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_4 [LEFT]
    <REJECTED> -> FeatureJoiner_3__Rejected_
FeatureJoiner_3__Rejected_: Logger
    LOG_FEATURE = LOG_ONLY
    MAXCOORDS = 20
    MAXFEATS = 20
    MESSAGE = Feature is:
    SEVERITY = INFO
FeatureJoiner_4
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_5 [LEFT]
    <REJECTED> -> FeatureJoiner_4__Rejected_
FeatureJoiner_4__Rejected_: Logger
    LOG_FEATURE = LOG_ONLY
    MAXCOORDS = 20
    MAXFEATS = 20
    MESSAGE = Feature is:
    SEVERITY = INFO
FeatureJoiner_5
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_6 [LEFT]
    <REJECTED> -> FeatureJoiner_5__Rejected_
FeatureJoiner_5__Rejected_: Logger
    LOG_FEATURE = LOG_ONLY
    MAXCOORDS = 20
    MAXFEATS = 20
    MESSAGE = Feature is:
    SEVERITY = INFO
FeatureJoiner_6
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_7 [LEFT]
    <REJECTED> -> FeatureJoiner_6__Rejected_
FeatureJoiner_6__Rejected_: Logger
    LOG_FEATURE = LOG_ONLY
    MAXCOORDS = 20
    MAXFEATS = 20
    MESSAGE = Feature is:
    SEVERITY = INFO
FeatureJoiner_7
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> FeatureJoiner_8 [LEFT]
    <REJECTED> -> FeatureJoiner_7__Rejected_
FeatureJoiner_7__Rejected_: Logger
    LOG_FEATURE = LOG_ONLY
    MAXCOORDS = 20
    MAXFEATS = 20
    MESSAGE = Feature is:
    SEVERITY = INFO
FeatureJoiner_8
    ATTR_CONFLICT_RES_LOOKUP = USE_LEFT
    GEOMETRY_HANDLING_LOOKUP = USE_LEFT
    JOIN_KEYS = _h3index _h3index AUTO
    JOIN_MODE = Inner
    ATTR_CONFLICT_RES = Prefer Left
    GEOMETRY_HANDLING = Prefer Left
    JOINED -> AttributeManager_11
    <REJECTED> -> FeatureJoiner_8__Rejected_

Bookmark: Faire un petit nettoyage
AttributeManager_11
    ATTR_TABLE:
      REMOVE max-min (real64)
      REMOVE x-min (real64)
      REMOVE Score_Police_Norm (real64)
      REMOVE SCORE_POLICE (real64)
      REMOVE _h3index (uint64)
      REMOVE nbr_poste_police.min (uint32)
      REMOVE nbr_poste_police.max (uint32)
      REMOVE Score_Crime_Norm (real64)
      REMOVE Score_crime (real64)
      REMOVE Nbr_crimes.min (uint32)
      REMOVE Nbr_crimes.max (uint32)
      REMOVE Score_Caserne_NORM (real64)
      REMOVE Score_Caserne (real64)
      REMOVE Nbr_Caserne_pompier.min (uint32)
      REMOVE Nbr_Caserne_pompier.max (uint32)
      REMOVE Score_Santé_Norm (real64)
      REMOVE Score_Santé (real64)
      REMOVE Nbr_hopitaux.min (uint32)
      REMOVE Nbr_hopitaux.max (uint32)
      REMOVE Score_college_norm (real64)
      REMOVE Score_Collége (real64)
      REMOVE Nbr_college.min (uint32)
      REMOVE Nbr_college.max (uint32)
      REMOVE Score_Universite_Norm (real64)
      REMOVE Score_Université (real64)
      REMOVE Nbr_université.min (uint32)
      REMOVE Nbr_université.max (uint32)
      REMOVE Score_Commerces_norm (real64)
      REMOVE Score_Commerces (real64)
      REMOVE nbr_resto_commerces.min (uint32)
      REMOVE nbr_resto_commerces.max (uint32)
      REMOVE Score_STM_Norm (real64)
      REMOVE Score_STM (real64)
      REMOVE Nbr_Arret_STM.min (uint32)
      REMOVE Nbr_Arret_STM.max (uint32)
      REMOVE Score_Parcs_Norm (real64)
      REMOVE Score_Parcs (real64)
      REMOVE Nbr_parc.min (uint32)
      REMOVE Nbr_parc.max (uint32)
    -> AttributeCreator_10

Bookmark: Calcul du score et des classe de quartiers
AttributeCreator_10
    ATTR_TABLE:
      SET_TO SCORE_QUARTIER (real64) = @Evaluate(@Evaluate(
            @Value(Score_Université_Ponderé) +
            @Value(Score_STM_pondéré) +
            @Value(Score_Santé_Pondere) +
            @Value(Score_Police_Pondéré) +
            @Value(Score_Parcs_ponderé) +
            @Value(Score_crime_ponderé) +
            @Value(Score_Commerces_Pondéré) +
            @Value(Score_Collége_Ponderé) +
            @Value(Score_Caserne_Ponderé)
        ))
      SET_TO Score_Securité (real64) = @Evaluate(@Value(Score_Caserne_Ponderé)+@Value(Score_Police_Pondéré)+@Value(Score_crime_ponderé))
      SET_TO Score_Education (real64) = @Evaluate(@Value(Score_Université_Ponderé)+@Value(Score_Collége_Ponderé))
      SET_TO Score_Attraction (real64) = @Evaluate(@Value(Score_Commerces_Pondéré)+@Value(Score_Parcs_ponderé))
    -> AttributeRangeMapper
AttributeRangeMapper
    IN_ATTR = SCORE_QUARTIER
    LUT = -0.21,0.08,Mediocre,0.08,0.62,Mauvais,0.62,1.43,Moyen,1.43,2.38,Bon,2.38,7,Excellent,,,
    OUT_ATTR = Classe
    -> TP2_H25 (writer POSTGIS_1)

FME custom transformer RandomPointGenerator
Creates random points within the area of entire input features.
This transformer accepts any features, but features that don't have area geometry will not be used.
Every resulting point will hold attributes that are held by an input area feature containing the point spatially.
If a point is contained by two or more areas in a same group (i.e. the areas are overlapping), the attributes will be migrated from any one of them.
Note:
This is an experimental transformer. Before adding it to your workspace, check enough whether the implementation is suitable to your purpose.
The implementation has been inspired by this thread in FME Community Answers.
Stratified random point in FME
http://fmepedia.safe.com/CommunityAnswers?id=906a0000000d3suAAA
Parameters
Group By:
Select attributes that should be used to group input features. 
Number of Points:
Specify the number of points to be created.
If you specified the "Group By" parameter, this parameter means the number of points per a group.
Otherwise, it means the total number of points to be created.

Parameters:
- GROUP_BY =   # " " Group By
- NUM_POINTS =   # Number of Points
- MIN_NUM = 10   # " " Minimum Number
- DENSIFY_FACTOR = 2   # Densify Factor

Area (input)
    -> GeometryFilter
GeometryFilter
    BREAK_AGG_BOOL = 0
    GEOM_PORTS = AREA ELLIPSE
    BREAK_AGG = No
    GEOM_PORT_NAMES = Area Ellipse
    AREA -> ParameterFetcher
    ELLIPSE -> ParameterFetcher
Note: Density of points for each box belonging to same group will be approximately identical.
Note: Sorter [Sorter] / Sorting By: randompointgenerator.group_id ALPHA ASCENDING
Sorter
    SORT_PARM = randompointgenerator.group_id ALPHA ASCENDING
    SORTED -> AttributeKeeper
    SORTED -> AttributeRemover
AttributeRemover
    REMOVE_ATTRS = randompointgenerator.group_by
    -> SpatialFilter [Filter]
BulkAttributeRemover
    ATTR_EXP = randompointgenerator.
    -> Point (output)
Point (output)

Bookmark: Add Group ID Attribute
ParameterFetcher
    ATTR_LIST = randompointgenerator.group_by {$(GROUP_BY)}
    -> TclCaller
TclCaller
    SRC:
      proc concatGroupByAttributeValues {} {
          set values {}
          foreach attr [FME_GetAttribute "randompointgenerator.group_by"] {
              lappend values [FME_GetAttribute $attr]
          }
          return [join $values {_}]
      }
    TCLPROG = concatGroupByAttributeValues
    VAL_ATTR = randompointgenerator.group_id
    -> Sorter

Bookmark: Flatten Areas and Calculate areas. Areas in a group will not overlap each other.
AttributeKeeper
    KEEP_ATTRS = randompointgenerator.group_id
    -> Deaggregator
Deaggregator
    EXPLODE_INSTANCES = No
    LIST_ATTR_MODE_LOOKUP = LEAN
    RECURSIVE = Yes
    SPLIT_COMPOSITES = No
    MODE = Flatten All Levels
    DEAGGREGATED -> AreaOnAreaOverlayer [AREA]
AreaOnAreaOverlayer
    GRP_BY = randompointgenerator.group_id
    AREA -> AreaCalculator
AreaCalculator
    AREA_ATTR = _area1
    AREA_TYPE = Plane Area
    MULT = 1
    -> BoundingBoxReplacer

Bookmark: Create Bounding Boxes and Calculate areas. Boxes in a group will not overlap each other.
BoundingBoxReplacer
    BBTYPE = BB
    BOXTYPE = Bounding Box
    BOX -> Dissolver
Dissolver
    ACCUM_INPUT_ATTRS_LOOKUP = NO
    GROUP_BY = randompointgenerator.group_id
    NO_OVRLP = No
    SUM = _area1
    ACCUM_INPUT_ATTRS = No
    AREA -> BoundingBoxReplacer_2
BoundingBoxReplacer_2
    BBTYPE = BB
    BOXTYPE = Bounding Box
    BOX -> AreaCalculator_2
AreaCalculator_2
    AREA_ATTR = _area2
    AREA_TYPE = Plane Area
    MULT = 1
    -> StatisticsCalculator

Bookmark: Compute Number of Points to be created for each Bounding Box
StatisticsCalculator
    COMPUTE_HISTOGRAM = NO
    GROUP_BY = randompointgenerator.group_id
    PREPEND_ATTR_NAME = Yes
    STATS_ATTRS = _area1 _area2
    SUM_ATTR = _sum
    PREPEND_ATTR_NAME_CHOICE = For all results
    COMPLETE -> BoundsExtractor
BoundsExtractor
    XMAX = _xmax
    XMIN = _xmin
    YMAX = _ymax
    YMIN = _ymin
    -> AttributeCreator_2
AttributeCreator_2
    ATTR_LIST = _num_group,"FME_CONDITIONAL:DEFAULT_VALUE'@Evaluate(1.0*$(NUM_POINTS)*@Value(_area2._sum)/@Value(_area1._sum))'BOOL_OP;OR;COMPOSITE_TEST;<Unused>;TEST @Evaluate(1.0*$(NUM_POINTS)*@Value(_area2._sum)/@Value(_area1._sum)) < $(MIN_NUM)'$(MIN_NUM)'FME_NUM_CONDITIONS2___",_ratio,@Evaluate(@double(@Value(_area2))/@Value(_area2._sum)),_width,@Evaluate(@Value(_xmax)-@Value(_xmin)),_height,@Evaluate(@Value(_ymax)-@Value(_ymin))
    -> ExpressionEvaluator
ExpressionEvaluator
    EXPRESSION = @int(@ceil($(DENSIFY_FACTOR)*@Value(_num_group)*@Value(_ratio)))
    VAL_ATTR = _num
    -> VertexCreator

Bookmark: Create Random Points for each Bounding Box
VertexCreator
    MODE = REPLACE
    XVAL = @Value(_xmin)
    YVAL = @Value(_ymin)
    MODE_NAME = Replace with Point
    -> AttributeKeeper_2
AttributeKeeper_2
    KEEP_ATTRS = randompointgenerator.group_id,_width,_height,_num
    -> Cloner
Cloner
    COPIES = @Value(_num)
    COPY -> Offsetter
Offsetter
    XOFF = @rand()*@Value(_width)
    YOFF = @rand()*@Value(_height)
    ZOFF = 0
    OFFSET -> AttributeKeeper_3
AttributeKeeper_3
    KEEP_ATTRS = randompointgenerator.group_id
    -> SpatialFilter [Candidate]

Bookmark: Take sample points within original areas for each group
SpatialFilter
    BASE_TYPE = Multiple Filters
    CURVE_BOUNDARY_RULE_PARAM = Default Rule
    GROUP_BY = randompointgenerator.group_id
    MERGE_ATTRS = Yes
    PASS_CRITERIA = Pass Against One Filter
    PREDICATES = INTERSECTS
    USE_BOUNDING_BOX = No
    PASSED -> ExpressionEvaluator_2
ExpressionEvaluator_2
    EXPRESSION = @rand()
    VAL_ATTR = randompointgenerator.rand
    -> Sorter_2
Sorter_2
    SORT_PARM = randompointgenerator.group_id ALPHA ASCENDING randompointgenerator.rand NUMERIC ASCENDING
    SORTED -> Sampler
Sampler
    GROUP_BY = randompointgenerator.group_id
    RATE = $(NUM_POINTS)
    SAMPLE_TYPE_MULTIPLIER = -1
    SAMPLE_TYPE_LONG = First N Features
    SAMPLED -> BulkAttributeRemover
